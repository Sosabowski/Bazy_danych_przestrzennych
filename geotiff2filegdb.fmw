FME workspace geotiff2filegdb.fmw
Title: fme_bdp

Parameters:
- SourceDataset_GEOTIFF = ""D:\rastry\HP.tif" "D:\rastry\HT.tif" "D:\rastry\HU.tif" "D:\rastry\HW.tif" "D:\rastry\HX.tif" "D:\rastry\HY.tif" "D:\rastry\HZ.tif" "D:\rastry\NA.tif" "D:\rastry\NB.tif" "D:\rastry\NC.tif" "D:\rastry\ND.tif" "D:\rastry\NF.tif" "D:\rastry\NG.tif" "D:\rastry\NH.tif" "D:\rastry\NJ.tif" "D:\rastry\NK.tif" "D:\rastry\NL.tif" "D:\rastry\NM.tif" "D:\rastry\NN.tif" "D:\rastry\NO.tif" "D:\rastry\NR.tif" "D:\rastry\NS.tif" "D:\rastry\NT.tif" "D:\rastry\NU.tif" "D:\rastry\NW.tif" "D:\rastry\NX.tif" "D:\rastry\NY.tif" "D:\rastry\NZ.tif" "D:\rastry\OV.tif" "D:\rastry\SC.tif" "D:\rastry\SD.tif" "D:\rastry\SE.tif" "D:\rastry\SH.tif" "D:\rastry\SJ.tif" "D:\rastry\SK.tif" "D:\rastry\SM.tif" "D:\rastry\SN.tif" "D:\rastry\SO.tif" "D:\rastry\SP.tif" "D:\rastry\SR.tif" "D:\rastry\SS.tif" "D:\rastry\ST.tif" "D:\rastry\SU.tif" "D:\rastry\SV.tif" "D:\rastry\SW.tif" "D:\rastry\SX.tif" "D:\rastry\SY.tif" "D:\rastry\SZ.tif" "D:\rastry\TA.tif" "D:\rastry\TF.tif" "D:\rastry\TG.tif" "D:\rastry\TL.tif" "D:\rastry\TM.tif" "D:\rastry\TQ.tif" "D:\rastry\TR.tif" "D:\rastry\TV.tif""   # Source GeoTIFF File(s) or URL(s)
- DestDataset_FILEGDB = D:\rastry\out   # File Geodatabase
- SourceDataset_OGCGEOPACKAGE = D:\raster2\Data\bdline_gb.gpkg   # GeoPackage File
- SourceDataset_GEOTIFF_3 = ""D:\rastry\HP.tif" "D:\rastry\HT.tif" "D:\rastry\HU.tif" "D:\rastry\HW.tif" "D:\rastry\HX.tif" "D:\rastry\HY.tif" "D:\rastry\HZ.tif" "D:\rastry\NA.tif" "D:\rastry\NB.tif" "D:\rastry\NC.tif" "D:\rastry\ND.tif" "D:\rastry\NF.tif" "D:\rastry\NG.tif" "D:\rastry\NH.tif" "D:\rastry\NJ.tif" "D:\rastry\NK.tif" "D:\rastry\NL.tif" "D:\rastry\NM.tif" "D:\rastry\NN.tif" "D:\rastry\NO.tif" "D:\rastry\NR.tif" "D:\rastry\NS.tif" "D:\rastry\NT.tif" "D:\rastry\NU.tif" "D:\rastry\NW.tif" "D:\rastry\NX.tif" "D:\rastry\NY.tif" "D:\rastry\NZ.tif" "D:\rastry\OV.tif" "D:\rastry\SC.tif" "D:\rastry\SD.tif" "D:\rastry\SE.tif" "D:\rastry\SH.tif" "D:\rastry\SJ.tif" "D:\rastry\SK.tif" "D:\rastry\SM.tif" "D:\rastry\SN.tif" "D:\rastry\SO.tif" "D:\rastry\SP.tif" "D:\rastry\SR.tif" "D:\rastry\SS.tif" "D:\rastry\ST.tif" "D:\rastry\SU.tif" "D:\rastry\SV.tif" "D:\rastry\SW.tif" "D:\rastry\SX.tif" "D:\rastry\SY.tif" "D:\rastry\SZ.tif" "D:\rastry\TA.tif" "D:\rastry\TF.tif" "D:\rastry\TG.tif" "D:\rastry\TL.tif" "D:\rastry\TM.tif" "D:\rastry\TQ.tif" "D:\rastry\TR.tif" "D:\rastry\TV.tif""   # Source GeoTIFF File(s) or URL(s)
- DestDataset_POSTGIS = cw9   # Connection

Readers:
- GEOTIFF_1: GEOTIFF from $(SourceDataset_GEOTIFF)
- OGCGEOPACKAGE_1: OGCGEOPACKAGE from $(SourceDataset_OGCGEOPACKAGE)
- GEOTIFF_2: GEOTIFF from $(SourceDataset_GEOTIFF_3)

Writers:
- FILEGDB_1: FILEGDB to $(DestDataset_FILEGDB)
- POSTGIS_1: POSTGIS to $(DestDataset_POSTGIS)

Creator
    GEOMTYPE = Geometry Object
    NUM = 1
    CREATED -> SQLExecutor [INITIATOR]
SQLExecutor
    COMBINE_ATTRS = Result Attributes Only
    COMBINE_GEOM = Initiator Geometry Only
    DATASET = cw9
    FORMAT = POSTGIS
    OUTPUT_FEATURES_DISPLAY = Schema and Data Features
    POSTGIS_CREATE_FEATURE_TABLES_FROM_DATA = Yes
    POSTGIS_DISABLE_COLLECTION_SPLITTING = yes
    POSTGIS_NAMED_CONNECTION = cw9
    POSTGIS_QUERY_FEATURE_TYPES_FOR_MERGE_FILTERS = Yes
    POSTGIS_READ_TIME_WITH_TIMEZONE = Yes
    POSTGIS_USE_TRUE_POSTGIS_TYPES = yes
    SQL_STATEMENT = CREATE TABLE public."e4" AS SELECT ST_Union(geom) From "public"."GEOTIFF"
    RESULT -> Inspector_6
Inspector_6
scotland_and_wales_region (reader OGCGEOPACKAGE_1)
    attributes: Name text(100), Area_Code text(3), Area_Description text(50), File_Name text(100), Feature_Serial_Number mediumint, Collection_Serial_Number mediumint, Global_Polygon_ID mediumint, Admin_Unit_ID mediumint, Census_Code text(9), Hectares double, Non_Inland_Area double, Area_Type_Code text(2), Area_Type_Description text(25), Non_Area_Type_Code text(3), Non_Area_Type_Description text(36), fid int,PrimaryKey
    -> TestFilter
    -> Inspector_4
Inspector_4
TestFilter
    DEFAULT_VALUE = <UNFILTERED>
    PASSED_TEST_GROUP_OUTPUT = FIRST
    TEST_LIST:
      "BOOL_OP,AND,COMPOSITE_TEST,""""""1 AND 2 AND 3"""""",TEST_CLAUSE,TEST @Value(Area_Code) = WPE
      TEST @Value(Feature_Serial_Number) != 1840
      TEST @Value(Feature_Serial_Number) != 1841",@Value(Area_Code) = WPE
    @Value(Area_Code) = WPE -> Dissolver
    @Value(Area_Code) = WPE -> SpatialFilter [Filter]
Dissolver
    ACCUM_INPUT_ATTRS = Use Attributes From One Feature
    CLEANING_TOLERANCE = Automatic
    CONNECT_Z_MODE = First Wins
    DEAGGREGATE_INPUT = Yes
    AREA -> Clipper [CLIPPER]
GEOTIFF (reader GEOTIFF_1)
    -> Reprojector
Reprojector
    DEST = EPSG:4326
    INTERPOLATION_TYPE_NAME = Nearest Neighbor
    RASTER_CELL_SIZE = Preserve Cells
    RASTER_TOLERANCE = 0.0
    REPROJECTED -> RasterExtentsCoercer
RasterExtentsCoercer
    EXTENTS_TYPE = Raster Extents
    EXTENTS -> Inspector
    EXTENTS -> FilePropertyExtractor
Inspector
FilePropertyExtractor
    FMT = FME Date/Time (%Y%m%d%H%M%S)
    PATH = D:\rastry\HP.tif
    -> AttributeCreator
    -> Inspector_2
Inspector_2
AttributeCreator
    ATTR_TABLE = SET_TO newname (varchar(200)) = @Value(_file_size)+"_"+@Value(fme_basename)
    -> GEOTIFF (writer FILEGDB_1)
    -> Inspector_3
Inspector_3
GEOTIFF (writer FILEGDB_1)
GEOTIFF (reader GEOTIFF_2)
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Clipper [CANDIDATE]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> RasterPaletteResolver
RasterPaletteResolver
    -> Exports (writer POSTGIS_1)
    -> Inspector_5
Inspector_5
Exports (writer POSTGIS_1)

FME custom transformer FilePropertyExtractor
Extracts basic properties of a file or a directory and adds these attributes to the feature.
    _file_type
    : holds "File" or "Directory", which indicates whether the specified path is a file or a directory.
    _file_size
    : holds the size of file/directory in bytes (total of file sizes if directory)
    _file_atime
    : holds the time of last access.
    _file_mtime
    : holds the time of last modification.
    _file_ctime
    : holds the time of creation on some systems (like Windows), or the time of last metadata change on other systems (like Unix).
    You can specify the format of "_file_atime", "_file_mtime", and "_file_ctime" via the "Date/Time Format" parameter.
    The input feature will be output from the 
    <Rejected>
    port if the specified file/directory does not exist, the path indicates a symbolic link, or an unexpected error has occurred. 
    This transformer contains a Python script, which was tested with both Python 2.7 and Python 3.4 interpreter.
Parameters
    File/Directory Path
    :
    Specify the path of a file or a directory.
    Date/Time Format
    :
    Specify a date/datetime/time format that should be applied to the values of "_file_atime", "_file_mtime", and "_file_ctime". 
    The format syntax is the same as the DateFormatter. See the help doc on the transformer.

Parameters:
- PATH =   # File/Directory Path
- FMT = FME Date/Time (%Y%m%d%H%M%S)

Input (input)
    -> ParameterFetcher
ParameterFetcher
    ATTR_LIST = __filepropertyextractor.path {$(PATH)}
    -> PythonCaller
PythonCaller
    NEW_ATTRIBUTES = _file_type _file_size _file_atime _file_mtime _file_ctime __filepropertyextractor.error
    PYTHONSOURCE:
      # 2016-05-25, Takashi Iijima, Original Implementation
      # 2020-01-28, Takashi Iijima, Calculate Directory Size as Total File Sizes under the Directory; Changed Default Python Interpreter to 3.6+

      import fme, fmeobjects
      import os
      def extractFileProperty(feature):
          def get_dir_size(path):
              total = 0
              for p in os.listdir(path):
                  full_path = os.path.join(path, p)
                  if os.path.isfile(full_path):
                      total += os.path.getsize(full_path)
                  elif os.path.isdir(full_path):
                      total += get_dir_size(full_path)
              return total
          try:
              path = feature.getAttribute('__filepropertyextractor.path')
              if os.path.exists(path) and not os.path.islink(path):
                  s = os.stat(path)
                  if os.path.isdir(path):
                      feature.setAttribute('_file_type', 'Directory')
                      feature.setAttribute('_file_size', get_dir_size(path))
                  else:
                      feature.setAttribute('_file_type', 'File')
                      feature.setAttribute('_file_size', s.st_size)
                  feature.setAttribute('_file_atime', int(s.st_atime))
                  feature.setAttribute('_file_mtime', int(s.st_mtime))
                  feature.setAttribute('_file_ctime', int(s.st_ctime))
              else:
                  raise Exception('specified file/directory does not exist')
          except Exception as ex:
              feature.setAttribute('__filepropertyextractor.error', '%s' % ex)
    PYTHONSYMBOL = extractFileProperty
    -> Tester
Tester
    BOOL_OP = OR
    TEST_CLAUSE = TEST __filepropertyextractor.error ATTRIBUTE_IS_MISSING ""
    TEST_MODE = Automatic
    PASSED -> AttributeRemover
    FAILED -> AttributeRemover_2
AttributeRemover
    REMOVE_ATTRS = __filepropertyextractor.path,__filepropertyextractor.error
    -> DateFormatter
DateFormatter
    DATE_ATTR = _file_ctime,_file_mtime,_file_atime
    FMT = $(FMT)
    INVALID_DATE_VALUE = _FME_NO_OP_
    SRCFMT = %s
    -> Output (output)
Output (output)
AttributeRemover_2
    REMOVE_ATTRS = _file_size,_file_type,_file_ctime,__filepropertyextractor.path,_file_mtime,_file_atime
    -> AttributeRenamer
AttributeRenamer
    ATTR_TABLE = RENAME_SET_DEFAULT __filepropertyextractor.error > _rejected_reason
    -> <Rejected> (output)
<Rejected> (output)
